(setq i 0)
(setq k 0)
(while (< i 10)
       ;(command "_.Line" '((* i 10) 0) '((* i 10) 100) "")
       (setq k (+ k i))
       (setq i (1+ i))
)
(initget "Yes No")
(setq reply (getkword "Transform line? [Yes/No]: "))
