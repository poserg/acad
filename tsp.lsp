(defun myfunc (x y lx ly st_x st_y koef / my_x my_y )
  (setq my_y y)
  (while (<= my_y (+ ly y))
	 (setq my_x x)
	 (while (<= my_x (+ lx x))
		(entmake (list (vl-list* 0 "LINE") (list 10 (- my_x koef) my_y) (list 11 (+ my_x koef) my_y)))
		(entmake (list (vl-list* 0 "LINE") (list 10 my_x (- my_y koef)) (list 11 my_x (+ my_y koef))))
		(setq my_x (+ my_x st_x))
		)
	 (setq my_y (+ my_y st_y))
	(princ)
  )
)
